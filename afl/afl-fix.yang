module afl-fix{
	yang-version 1.1;
	namespace "urn:dpack:afl-fix";
	prefix "afl";

	organization "Test Inc.";
	contact "joe@test.com";
	description
		"The module for entities implementing the fix sample.";

	revision 2023-02-28 {
		description "Initial revision.";
		reference "";
	}

	container sample {
		presence "keyword mandatory if mandatory leaf is present";
		description "The sample main container";
		leaf u8 {
			type uint8;
			description "Sample uint8 leaf";
		}
		leaf u16 {
			type uint16;
			description "Sample uint16 leaf";
		}
		leaf u32 {
			type uint32 {
				range "1..50 | 700";
			}
			description "Sample uint32 leaf";
		}
		leaf u64 {
			type uint64;
			description "Sample uint64 leaf";
		}
		leaf s8 {
			type int8;
			description "Sample int8 leaf";
		}
		leaf s16 {
			type int16;
			default 16;
			description "Sample int16 leaf with default value";
		}
		leaf s32 {
			type int32;
			description "Sample int32 leaf";
		}
		leaf s64 {
			type int64;
			mandatory true;
			description "Sample int64 leaf";
		}
		leaf u32ob {
			type uint32;
			status obsolete;
			description "Sample uint32 leaf obsolete";
		}
		leaf u32obmand {
			type uint32;
			mandatory true;
			status obsolete;
			description "Sample uint32 leaf mandatory obsolete";
		}
		leaf boolean {
			type boolean;
			description "Sample boolean leaf";
		}
		leaf string {
			type string {
				pattern "test.*";
				pattern ".*string";
				pattern ".*afl.*" {
					modifier "invert-match";
				}
			}
			description "Sample boolean leaf";
		}
		leaf stringobamd {
			type string;
			mandatory true;
			status obsolete;
			description "Sample boolean leaf";
		}
		leaf stringdflt {
			type string;
			default "this is default value for test";
			description "Sample boolean leaf";
		}
	}
}
